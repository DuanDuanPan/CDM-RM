## REQ-ENG-0001
- 发动机在 ISA 海平面静止条件下，应提供不小于 120 kN 的最大起飞推力。
- [EN] Under ISA sea-level static conditions, engine shall deliver ≥120 kN takeoff thrust.

## REQ-ENG-0002
- 巡航工况下单位推力燃油消耗（TSFC）应不高于 0.62 kg/(kN·h)。
- [EN] Cruise TSFC shall be ≤ 0.62 kg/(kN·h).

## REQ-ENG-0003
- 满足 ICAO CAEP/8 排放限值（NOx/CO/HC/烟度）。
- [EN] Comply with ICAO CAEP/8 emission limits (NOx/CO/HC/Smoke).
